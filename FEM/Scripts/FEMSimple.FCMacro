import FemGui
import FemToolsCcx
import Part
import Fem
import FemGmshTools
import ObjectsFem
import pickle
import numpy as np
import itertools
import utility

import vector_calc as vc
reload(vc)


data_path = "C:\\Users\\Administrator\\Google Drive\\Windows\\Research\\Project\\FEM\\Results\\data"
# to run script open FreeCAD
# create empty project and use buildScene()
# or open selfmadeAFO.FCStd\cylinderAFO.FCStd and set the analysis to active

# and enter in ptyhonconsole following command:
# execfile("C:\Users\Administrator\Google Drive\Windows\Research\Project\FEM\Scripts\FEMSimple.FCMacro")


def clearAll():
    if App.ActiveDocument == None:
        App.newDocument("Test")
        App.setActiveDocument("Test")
    doc = App.ActiveDocument
    for obj in doc.Objects:
        doc.removeObject(obj.Label)


def buildScene():
    clearAll()
    doc = App.ActiveDocument

    # some geometry
    box = Part.makeBox(1, 1, 1)

    box_obj = App.ActiveDocument.addObject('Part::Box', 'Box')
    box_obj.Length = 4
    box_obj.Height = 20

    # change box and remesh, we do not need a new instance of gmsh_mesh class

    # error = gmsh_mesh.create_mesh()
    # print error

    # App.ActiveDocument.recompute()
    # change mesh params and remesh, we need a new instance of gmsh_mesh class
    # femmesh_obj_gmsh.CharacteristicLengthMax = 1
    # gmsh_mesh = FemGmshTools.FemGmshTools(femmesh_obj_gmsh)
    # error = gmsh_mesh.create_mesh()
    # print error
    # App.ActiveDocument.recompute()

    # analysis
    analysis_object = ObjectsFem.makeAnalysis("Analysis")
    # solver
    solver_object = ObjectsFem.makeSolverCalculix('CalculiX')
    solver_object.AnalysisType = 'static'
    solver_object.GeometricalNonlinearity = 'linear'
    # solver_object.SteadyState = True
    # solver_object.Accurency = 0.01
    # solver_object.EigenmodeNumber = 1
    solver_object.ThermoMechSteadyState = True
    solver_object.MatrixSolverType = 'default'
    solver_object.IterationsControlParameterTimeUse = False
    doc.Analysis.Member = doc.Analysis.Member + [solver_object]

    # fixed_constraint
    fixed_constraint = doc.addObject(
        "Fem::ConstraintFixed", "FemConstraintFixed")
    fixed_constraint.References = [(doc.Box, "Face5s")]
    doc.Analysis.Member = doc.Analysis.Member + [fixed_constraint]

    # import MechanicalMaterial
    material_object = ObjectsFem.makeMaterialSolid("SolidMaterial")
    mat = material_object.Material
    mat['Name'] = "Steel-Generic"
    mat['YoungsModulus'] = "210000 MPa"
    mat['PoissonRatio'] = "0.30"
    mat['Density'] = "7900 kg/m^3"
    material_object.Material = mat
    doc.Analysis.Member = doc.Analysis.Member + [material_object]

    # make an initial FEM mesh
    femmesh_obj_gmsh = ObjectsFem.makeMeshGmsh('MyGMSHMeshObj')
    femmesh_obj_gmsh.Part = box_obj
    App.ActiveDocument.recompute()
    gmsh_mesh = FemGmshTools.FemGmshTools(femmesh_obj_gmsh)
    error = gmsh_mesh.create_mesh()
    print(error)
    App.ActiveDocument.recompute()

    # mesh
    doc.Analysis.Member = doc.Analysis.Member + [doc.MyGMSHMeshObj]

    # recompute doc
    doc.recompute()
    # set displacements
    doc = App.ActiveDocument
    # displacement constraint setup
    displ_constraint = doc.addObject(
        "Fem::ConstraintDisplacement", "FemConstraintDisplacement")
    displ_constraint.References = [(doc.Box, "Face6")]
    displ_constraint.xFree = False
    displ_constraint.yFree = False
    displ_constraint.zFree = False
    doc.Analysis.Member = doc.Analysis.Member + [displ_constraint]
    return femmesh_obj_gmsh.FemMesh, box_obj.Shape, displ_constraint


def runFEA(femmesh, shape, displ_constraint,result_object_name, n_disp=1, disp=(-0.1,0.1)):

    # FemGui.setActiveAnalysis(FreeCAD.ActiveDocument.Analysis)
    fea = FemToolsCcx.FemToolsCcx()

    
    # displacment is in cm
    displacements = np.random.uniform(disp[0], disp[1], size=(n_disp, 2))
    surface_normals = vc.getNormalOfFemmeshSurface(femmesh)
    # calculate
    mesh_normal_CS = [vc.rand_triangle_coord_system(
        n) for n in surface_normals]
    surface_strains = []
    surface_proj_strains = []
    all_strains = []
    #save the triangles which make up the surface of the femmesh in the form of a node list
    faces_as_nodes = [femmesh.getElementNodes(face) for topoface in shape.Faces for face in femmesh.getFacesByFace(topoface)]
    nodes_coord = dict([(i, vc.vectorToNPArr(femmesh.getNodeById(i))) for i in femmesh.Nodes])
    for disp in displacements:
        displ_constraint.xDisplacement = disp[0]
        displ_constraint.yDisplacement = disp[1]
        displ_constraint.zDisplacement = 0

        fea.update_objects()
        # a string is returned, the string should be empty
        fea.check_prerequisites()
        fea.reset_all()
        fea.run()

        fea.load_results()
        result_object =  App.ActiveDocument.getObject(result_object_name)

        # run the analysis
        # all strains
        #first index strains according to node index
        #than extract for each node
        indexed_strains = dict([(n,vc.vectorToNPArr(v))
                            for n,v in zip(femmesh.Nodes,result_object.StrainVectors)])
        all_strains.append(indexed_strains)

    return list(displacements),nodes_coord,faces_as_nodes, all_strains


def print_results(all_strains, disp_list, nodes_coord,faces_as_nodes):
    # convert to numpy array
    with open(data_path + "\\all_strain_list" + "_" + scene_name + ".pickle", 'wb') as handle:
        pickle.dump(all_strains, handle, protocol=pickle.HIGHEST_PROTOCOL)
    with open(data_path + "\\displacement_list" +"_" + scene_name + ".pickle", 'wb') as handle:
        pickle.dump(disp_list, handle, protocol=pickle.HIGHEST_PROTOCOL)
    with open(data_path + "\\nodes_coord" +"_" + scene_name+ ".pickle", 'wb') as handle:
        pickle.dump(nodes_coord, handle, protocol=pickle.HIGHEST_PROTOCOL)
    with open(data_path + "\\faces_as_nodes" +"_" + scene_name+ ".pickle", 'wb') as handle:
        pickle.dump(faces_as_nodes, handle, protocol=pickle.HIGHEST_PROTOCOL)
    


#femmesh, shape,displ_constraint= buildScene()
# to be used on self built afo scene
scene_name="simple_afo"
if scene_name=="simple_afo":
    femmesh = App.ActiveDocument.getObject(
        "FEMMeshGMSH001").FemMesh
    shape = App.ActiveDocument.getObject(
        "Fusion001001").Shape
    displ_constraint = App.ActiveDocument.getObject(
        "FemConstraintDisplacement")
    result_object_name = "CalculiX_static_results"
    disp=(-0.16,0.16)
# cylinder project
elif scene_name=="cylinder":
    femmesh = App.ActiveDocument.FEMMeshGMSH.FemMesh
    shape = App.ActiveDocument.Cylinder.Shape
    result_object_name = "CalculiX_static_results"
    displ_constraint = App.ActiveDocument.getObject(
        "FemConstraintDisplacement")
    disp=(-0.16,0.16)
elif scene_name=="simple_afo_big":
    femmesh = App.ActiveDocument.FEMMeshGMSH.FemMesh
    shape = App.ActiveDocument.Scale.Shape
    result_object_name = "CalculiX_static_results"
    displ_constraint = App.ActiveDocument.getObject(
        "FemConstraintDisplacement")
    disp=(-4,2)
elif scene_name=="cube":
    femmesh = App.ActiveDocument.getObject(
        "FEMMeshGMSH001").FemMesh
    shape = App.ActiveDocument.Box.Shape
    result_object_name = "CalculiX_static_results001"
    displ_constraint = App.ActiveDocument.getObject(
        "FemConstraintDisplacement001")
elif scene_name=="rot_cube":
    femmesh = App.ActiveDocument.getObject(
        "FEMMeshGMSH").FemMesh
    shape = App.ActiveDocument.BooleanFragments.Shape
    result_object_name = "CalculiX_static_results"
    displ_constraint = App.ActiveDocument.getObject(
        "FemConstraintDisplacement")
    disp=(-0.3,0.3)


# the number of displacements thus number of points generated
n_disp = 1000

displacements, nodes_coord,faces_as_nodes, all_strains, = runFEA(femmesh, shape, displ_constraint, result_object_name,
                                                                           n_disp=n_disp,disp=disp)
print_results(all_strains, displacements, nodes_coord,faces_as_nodes)


# # post processing of the result
# # femmesh_obj_gmsh.ViewObject.setNodeDisplacementByVectors(result_object.NodeNumbers, result_object.DisplacementVectors)
# print(strains)
# App.ActiveDocument.MyGMSHMeshObj.ViewObject.setNodeColorByScalars(
#     femmesh.Nodes,
#                     App.ActiveDocument.getObject("CalculiX_static_results").StressVectors)
# # App.ActiveDocument.MyGMSHMeshObj.ViewObject.setNodeColorByScalars(rand_nodes, strains[0])
# App.ActiveDocument.getObject(
#     "FEMMeshGMSH001").HighlightedNodes = list(range(20))
# femmesh_obj_gmsh.ViewObject.applyDisplacement(10)
