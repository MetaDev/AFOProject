import Fem
femmesh = Fem.FemMesh()

# nodes
femmesh.addNode(0.0, 0.0, 0.0, 1)
femmesh.addNode(0.0, 100.0, 0.0, 2)
femmesh.addNode(100.0, 0.0, 0.0, 3)
femmesh.addNode(100.0, 100.0, 0.0, 4)
femmesh.addNode(0.0, 50.0, 0.0, 5)
femmesh.addNode(0.0, 25.0, 0.0, 6)
femmesh.addNode(0.0, 75.0, 0.0, 7)
femmesh.addNode(50.0, 0.0, 0.0, 8)
femmesh.addNode(25.0, 0.0, 0.0, 9)
femmesh.addNode(75.0, 0.0, 0.0, 10)
femmesh.addNode(100.0, 50.0, 0.0, 11)
femmesh.addNode(100.0, 25.0, 0.0, 12)
femmesh.addNode(100.0, 75.0, 0.0, 13)
femmesh.addNode(50.0, 100.0, 0.0, 14)
femmesh.addNode(25.0, 100.0, 0.0, 15)
femmesh.addNode(75.0, 100.0, 0.0, 16)
femmesh.addNode(50.0, 50.0, 0.0, 17)
femmesh.addNode(25.0, 25.0, 0.0, 18)
femmesh.addNode(25.0, 75.0, 0.0, 19)
femmesh.addNode(75.0, 25.0, 0.0, 20)
femmesh.addNode(75.0, 75.0, 0.0, 21)
femmesh.addNode(12.5, 12.5, 0.0, 22)
femmesh.addNode(12.5, 37.5, 0.0, 23)
femmesh.addNode(37.5, 12.5, 0.0, 24)
femmesh.addNode(12.5, 62.5, 0.0, 25)
femmesh.addNode(12.5, 87.5, 0.0, 26)
femmesh.addNode(37.5, 87.5, 0.0, 27)
femmesh.addNode(87.5, 12.5, 0.0, 28)
femmesh.addNode(62.5, 12.5, 0.0, 29)
femmesh.addNode(87.5, 37.5, 0.0, 30)
femmesh.addNode(87.5, 87.5, 0.0, 31)
femmesh.addNode(87.5, 62.5, 0.0, 32)
femmesh.addNode(62.5, 87.5, 0.0, 33)
femmesh.addNode(37.5, 37.5, 0.0, 34)
femmesh.addNode(25.0, 50.0, 0.0, 35)
femmesh.addNode(37.5, 62.5, 0.0, 36)
femmesh.addNode(50.0, 25.0, 0.0, 37)
femmesh.addNode(62.5, 37.5, 0.0, 38)
femmesh.addNode(75.0, 50.0, 0.0, 39)
femmesh.addNode(62.5, 62.5, 0.0, 40)
femmesh.addNode(50.0, 75.0, 0.0, 41)


# elements
femmesh.addFace([1L, 18L, 5L, 22L, 23L, 6L], 9)
femmesh.addFace([1L, 8L, 18L, 9L, 24L, 22L], 10)
femmesh.addFace([2L, 5L, 19L, 7L, 25L, 26L], 11)
femmesh.addFace([2L, 19L, 14L, 26L, 27L, 15L], 12)
femmesh.addFace([3L, 20L, 8L, 28L, 29L, 10L], 13)
femmesh.addFace([3L, 11L, 20L, 12L, 30L, 28L], 14)
femmesh.addFace([4L, 21L, 11L, 31L, 32L, 13L], 15)
femmesh.addFace([4L, 14L, 21L, 16L, 33L, 31L], 16)
femmesh.addFace([5L, 18L, 17L, 23L, 34L, 35L], 17)
femmesh.addFace([5L, 17L, 19L, 35L, 36L, 25L], 18)
femmesh.addFace([8L, 17L, 18L, 37L, 34L, 24L], 19)
femmesh.addFace([8L, 20L, 17L, 29L, 38L, 37L], 20)
femmesh.addFace([11L, 17L, 20L, 39L, 38L, 30L], 21)
femmesh.addFace([11L, 21L, 17L, 32L, 40L, 39L], 22)
femmesh.addFace([14L, 19L, 17L, 27L, 36L, 41L], 23)
femmesh.addFace([14L, 17L, 21L, 41L, 40L, 33L], 24)

femmesh.addNode(0.0, 0.0, 1.0, 42)
# show FEM mesh
Fem.show(femmesh)



Gui.ActiveDocument.Mesh.HighlightedNodes = [42]
